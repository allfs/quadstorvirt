--	QUADStor Management Information Base (MIB) file

	QUADSTOR-TRAPS-MIB DEFINITIONS ::= BEGIN

	IMPORTS
		MODULE-IDENTITY, OBJECT-TYPE, NOTIFICATION-TYPE
			FROM SNMPv2-SMI
    		DisplayString
			FROM SNMPv2-TC
		MODULE-COMPLIANCE, OBJECT-GROUP, NOTIFICATION-GROUP
			FROM SNMPv2-CONF
		quadstorMIBs
			FROM QUADSTOR-REG
		;

quadstorMIB MODULE-IDENTITY
	LAST-UPDATED "201302151200Z"
	ORGANIZATION "QUADStor Systems"
	CONTACT-INFO
		"support@quadstor.com"
	DESCRIPTION
		"This module defines MIB objects to describe the traps generated by the QUADStor system"
	REVISION "201302151200Z" -- 15 Feb 2013 12:00
	DESCRIPTION
		"Sanity Check MIB for syntax errors"
	::= {quadstorMIBs 1}

quadstorTraps		OBJECT IDENTIFIER ::= { quadstorMIB 0 }
quadstorObjects		OBJECT IDENTIFIER ::= { quadstorMIB 1 }
quadstorConformance	OBJECT IDENTIFIER ::= { quadstorMIB 2 } 

notifyType		OBJECT-TYPE
	SYNTAX		INTEGER {
			information(1),
			warning(2),
			error(3)
	}
	MAX-ACCESS	read-only
	STATUS		current
	DESCRIPTION
		"Type of notification - Information,Warning,Error"
	::= { quadstorObjects 1 }


notifyMessage		OBJECT-TYPE
	SYNTAX		DisplayString(SIZE (0..256))
	MAX-ACCESS	read-only
	STATUS		current
	DESCRIPTION
		"Notification message"
	::= { quadstorObjects 2 }

quadstorNotification	NOTIFICATION-TYPE
	OBJECTS		{ notifyType, notifyMessage }
	STATUS		current
	DESCRIPTION
		"Generic trap sent for notifications"
	::= {quadstorTraps 2}

quadstorCompliances	OBJECT IDENTIFIER ::= { quadstorConformance 1 }
quadstorGroups		OBJECT IDENTIFIER ::= { quadstorConformance 2 }

--
-- quadstor Compliance
--

quadstorCompilance	MODULE-COMPLIANCE
	STATUS		current
	DESCRIPTION
		"All objects defined in this MIB need to be defined"
	MODULE
	MANDATORY-GROUPS {
		quadstorTrapsGroup, quadstorObjectsGroup
	}
	::= {quadstorCompliances 1 }

quadstorObjectsGroup	OBJECT-GROUP
	OBJECTS		{ notifyType, notifyMessage } 

	STATUS	current
	DESCRIPTION
		"The objects defined by this MIB "
	::= { quadstorGroups 1 }

quadstorTrapsGroup	NOTIFICATION-GROUP

	NOTIFICATIONS {
		quadstorNotification
	}
	STATUS	current
	DESCRIPTION
		"Thet traps defined by this MIB "
	::= { quadstorGroups 2 }

END
